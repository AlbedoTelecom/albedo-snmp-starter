ATSL-NETTIME-MIB DEFINITIONS ::= BEGIN

--
-- Albedo Telecom Net.Time MiB
--

IMPORTS
    MODULE-IDENTITY                                FROM SNMPv2-SMI
    atslProduct                                    FROM ATSL-MIB;

atslNetTime MODULE-IDENTITY
    LAST-UPDATED "202404020000Z" -- 2 April, 2024
    ORGANIZATION "www.albedotelecom.com"
    CONTACT-INFO
        "Francisco J. Hens
         fhr@albedotelecom.com

         Tel: +34 932 212 873
         Fax: +34 932 210 924

         ALBEDO Telecom SL
         C/ Joan d'Austria 112;
         08018 Barcelona - Spain"

    DESCRIPTION
        "This MIB module defines resources for accessing Albedo Telecom
        Net.Time objets."
	REVISION     "202404020000Z" -- 2 April, 2024
    DESCRIPTION
        "Draft 1 public."

    ::= { atslProduct 1 }

END
