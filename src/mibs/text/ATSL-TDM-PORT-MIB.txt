ATSL-TDM-PORT-MIB DEFINITIONS ::= BEGIN

--
-- ATSL MIB objects for TDM test port configuration.
--

IMPORTS
    MODULE-IDENTITY, OBJECT-TYPE, Unsigned32              FROM SNMPv2-SMI
    TEXTUAL-CONVENTION, DisplayString, TruthValue,
    RowStatus                                             FROM SNMPv2-TC
    atslGeneral, TableIndex, Word32, TestPattern          FROM ATSL-MIB;

 tdmPort MODULE-IDENTITY
    LAST-UPDATED "201707170000Z" -- 17 July, 2017
    ORGANIZATION "www.albedotelecom.com"
    CONTACT-INFO    
        "Francisco J. Hens
         fhr@albedotelecom.com

         Tel: +34 932 212 873
         Fax: +34 932 210 924

         ALBEDO Telecom SL
         C/ Joan d'Austria 112;
         08018 Barcelona - Spain"
    DESCRIPTION
        "This MIB defines configuration fields and tables required for
         configuration of a generic TDM test port. TDM technology defines
         fixed duration time intervals for delivery of digital data. TDM frames
         are switched by special TDM devices capable to add and drop digitally
         encoded data to / from time slots or merge the content of time slots
         from different input frames into one or several output interfaces. TDM
         technology dates from the XX century and it is very well suited for
         telephony applications but it can be used in data applications as well.

         This MIB is compatible with the TDM interfaces defined in ITU-T G.703,
         including the 2048 kb/s interface (E1) and the variable bit rate 
         co-directional, contra-directional and centralized interfaces. Other
         supported transmission standards are the ones collectively known as
         'data communications' interfaces, including the ITU-T V.11, V.24, V.35,
         V.36, EIA530 and EIA530A. Finally, the MIB is compatible with the
         standard IEEE C37.94 interface that defines an optical interface with
         application in the power industry.

         Scalars

         - 'tdmPortEnable': Starts / Stops traffic generation in the managed
           entity. The action starts generation through all the available
           blocks. The number of monitoring blocks may not be the same for
           different managed entities and it may be that there is only one
           monitoring block for some of them.

         - 'tdmPortMode': Configures the general operation mode for the agent.
           It determines the functionality, supported frame formats, protocols
           and tests. Some configuration fields defined by several OIDs defined
           in this MIB may not be available in some configuration modes. The
           operation mode usually involves automatic re-configuration of all the
           available test ports in the agent.

         Tables

         - 'tdmPortModeTable': This table can be used for test port management
           in the agent. It contains one row per each test port and it can be
           used to configure the interface in ports supporting multiple
           interface operation. For test ports supporting only a single
           operation mode, this table enables the SNMP manager to read
           information about the interface. Depending on the interface types
           configured in this table some OIDs may be enabled or disabled in
           other tables or MIBs.

         - 'tdmPortPatternTable': This table configures the test pattern format
           for traffic synthetic traffic internally generated by the agent. Most
           of the agents with frame generation capabilities generate synthetic
           traffic with configurable content. The bit stream transmitted by
           frame generators  enable them to carry out different kinds of
           measurements including Bit Error Rate (BER), latency and several
           other derived parameters.

         ALBEDO Telecom testers currently implementing this MIB module are
         listed below:

         - AT-2048 E1 / Datacom Tester.
         - Ether.Genius GbE / E1 / Datacom / Jitter & Wander Tester.
         - Ether10.Genius 10GbE / E1/T1 / Datacom / C37.94 Tester"
    REVISION     "201707170000Z" -- 17 July, 2017
    DESCRIPTION
        "- References to IEEE C37.94 are deleted from the 'datacomEndpoint' 
           mode and two new modes are defined for IEEE C37.94 operation."
    REVISION "201702010000Z" -- 1 February, 2017
    DESCRIPTION
    	"The 'tdmPortMode' OID has been marked as deprecated." 

    REVISION     "201609200000Z" -- 20 September 2016
    DESCRIPTION
        "The tester complatibility list has been enlarged to include
         Ether10.Genius. The MIB DESCRIPTION has been edited to mention
         support of the T1 interface (1544 kb/s).

         The 'e1Monitor', 'e1Endpoint' and 'e1Through' descriptors from the
         'operationMode' textual conventions have been renamed to the generic
         'tdmMonitor', ' tdmEndpoint' and 'tdmThrough'.

         A new interface type, 'ansit1', has been added to the 'TdmInterface'
         textual convention to add compatibility with the ANSI T1.102 (T1)
         interface.

         In previous version new framing structures were defined in the MIB
         (T1 framings, IEEE C37.94 framings) but they were never added to the
         'FrameType' textual convention. This problem is now fixed.

         Two textual conventions are migrated from the ATSL-E1-PORT-MIB: 'ABCD'
         and 'TimeSlotUse'."
    REVISION     "201602050000Z" -- 5 February, 2016
    DESCRIPTION
        "Includes a new 'FrameType' textual convention to define different kinds
         of frame structure. This textual convention replaces and extends the
         older textual convention with the same name but available from the 
         ATSL-E1-PORT-MIB module.

         'FrameType' now adds the T1 framings (SF and ESF) and the IEEE C37.94
         framings to the ITU-T G.704 frame structures for E1."
    REVISION     "201412230000Z" -- 23 December, 2014
    DESCRIPTION
        "The MIB name has been changed to 'ATSL-TDM-PORT-MIB.txt' from
         'ATSL-TDM-GENERATOR-MIB.txt'. Module identity has changed to 'tdmPort'.
         OID prefixes and comments have been upgraded to match the new
         terminology.

         The new 'e0Endpoint' operation mode has been included in the
         'OperationMode' textual convention that enables configuration of ITU-T
         G.703 co-directional, contra-directional and centralized interfaces
         in AT-2048 agents.

         The 'tdmGenModeTable' and 'tdmGenLineTable' is not used in the new
         version of the MIB. These tables have been exported to the 
         ATSL-E1-PORT-MIB."
    REVISION     "201409090000Z" -- 09 September, 2014
    DESCRIPTION
        "Draft 1 public. Latest version available"

    ::= { atslGeneral 19 }

--
-- Textual conventions
--

OperationMode ::=TEXTUAL-CONVENTION
    STATUS            current
    DESCRIPTION
        "Defines different operation modes for the agent. This setting is shared
         by all E1 ports and traffic generation and analysis modules available
         in the the managed device. Some operation modes define specific uses
         for the transmitter and the receiver and some of them may involve non
         trivial relationship between test ports. For example, if supported, the
         pass-through mode may be used to forward traffic between test ports.
         The available configuration choices currently supported by this textual
         convention are:

         - 'tdmMonitor': When the agent is operating in 'tdmMonitor' mode, the
           transmitter is switched off in all affected test ports. This mode is
           suitable for analysis of life signals without disturbing the network.
           Applications requiring this mode are frequency or level monitoring,
           alarm monitoring or some kinds of in service performance monitoring.
           Often, the 'tdmMonitor' mode has to be combined with high impedance
           settings to avoid disturbing the line but configuring monitor does
           not automatically enables high impedance operation in the tester.

         - 'tdmEndpoint': If the agent is configured in 'tdmEndpoint' mode, then
           it emulates a TDM network terminating point. In this mode the
           generator sends a test signal to the DUT / SUT and the analyser
           receives a different signal (which may be the test signal once it has
           been transmitted through the DUT / SUT. This mode is used for
           transparency testing, BER testing and out of service performance
           monitoring.

         - 'tdmThrough': The 'tdmThrough' mode is suited for unidirectional or
           bidirectional intrusive monitoring. The signal is received in a TDM
           test port and it is either dropped to an analysis block or forwarded
           to the TDM transmitter in a second test port. Some agents may also
           support adding signals from internal traffic generation blocks.

         - 'e0Endpoint': This mode is suitable for generation and analysis of
           one of the variable bit rate interfaces defined in ITU-T G.703.
           The E0 name is referred to one of the co-directional,
           contra-directional or centralized interfaces. These are synchronious
           interfaces, the main difference between them being the mechanism used
           to distribute the clock.

         - 'datacomEndpoint': Use the Datacom endpoint mode to generate and
           analyse V.24/V.28, X.21/V.11, V.35, V.36 and EIA-530 datacom signals.
           In some agents, this mode is used for generation and analysis of
           G.703 co-directional. When the agent is configured in this mode, it 
           replaces either the DTE or the DCE along with their data and control 
           circuits. 

         - 'datacomMonitor': The Datacom monitor mode analyses V.24/V.28,
           X.21/V.11, V.35, V.36 and EIA-530 datacom signals without disturbing
           communications between the DTE and DCE. If this mode is configured,
           the Smart Serial connector is used. The specific connector for the
           DTE and the DCE is available through two adaptor cables.

         - 'c3794Endpoint': Configures the agent as a IEEE C37.94 termination
           point. IEEE C37.94 standard constitutes a communications interface 
           for interconnection of power protection equipment (protection 
           relays) and transmission equipment using two multi-mode optical 
           fibres.

         - 'c3794Monitor': When the agent is operating in C37.94 monitor mode, 
           the optical transmitter is switched off. This mode is suitable for 
           analysis of life signals without disturbing the network. Applications 
           requiring this mode are frequency or level monitoring and alarm 
           monitoring.

         - 'external': This operation mode enables the agent to implement
           external operation modes. These modes are beyond this MIB and may
           correspond to different measurements heterogeneous combinations of
           test ports, advanced protocol generation or any other."
    SYNTAX            INTEGER {
                          tdmMonitor (0),
                          tdmEndpoint (1),
                          tdmThrough (2),
                          e0Endpoint (3),
                          dataEndpoint (4),
                          dataMonitor (5),
                          c3794Endpoint (6),
                          c3794Monitor (7),
                          external (8)
                      }

TdmInterface ::=TEXTUAL-CONVENTION
    STATUS            current
    DESCRIPTION
        "Defines different interfaces for a test port. This textual convention
         can be applied to a multi-function primary test port and to secondary,
         low rate ports acting as add and drop interfaces. The currently
         accepted port modes are listed below:

         - 'none':  The transmitter and receiver are both disabled. When
           disabled, the port is unable to send or receive information.

         - 'g703e1': The port is configured to send / receive information at
           2048 kb/s as G.703 generator / analyser.

         - 'clock': Clock input and / or output available for tests requiring
           external synchronization. Format of the clock may be 2048 kHz,
           2048 kb/s, 1544 kHz, 1544 kb/s, 10 MHz, 1 pps or any other but
           configuration of this interface is beyond the purpose of this MIB.

         - 'g703e0': Configures the multi-purpose test port of the add and drop
           port for generation and analysis of one of the variable bit rate
           interfaces defined in ITU-T G.703. Detailed configuration of a
           G703 / E0 interface is beyond the purpose of this MIB.

         - 'datacom': Generic datacom interface, It refers to a data
           communications port without specifying the standard. It could be any
           of the data communications interfaces supported by the agent such as
           ITU-T V.11, V.24, V.35, V.36, EIA530 and EIA530A.

         - 'v11': Sets the X.21 / V.11 datacom interface. The X.21 / V.11 is
           an ITU-T specification of a data communications system for
           differential transmission.

         - 'v24': Sets the V.24 / V.28 datacom interface. It is essentially the
           same that RS-232C and EIA-232 standards. V.24 has an asynchronous
           operation mode for low speed, low reach applications and a
           synchronous operation mode that is typically used for transporting
           HDLC, X.25 or PPP applications. V.24 uses unbalanced transmission for
           all circuits.

         - 'v35': Sets the V.35 datacom interface. The V.35 uses
           differential transmission for the clock and data signals while 
           signals which normally incur a minimum state changes are unbalanced.

         - 'v36': Sets the V.36 interface. This interface is also referred as
           RS-449. This is a differential communications interface. It is used
           when either long reach or high speed is required. It also offers good
           noise immunity in environments with high levels of EMI.

         - 'eia530': Sets the EIA-530 or RS-530 interface. Most EIA-530 signals
           conform with the RS-449 requirements as well. Applications are
           similar to the RS-449 applications.

         - 'eia530a': Sets the EIA-530A datacom interface. EIA-530A is similar
           but incompatible with EIA-530. All EIA-530 circuits are balanced but
           some EIA-530A control circuits are unbalanced.

         - 'c3794': Configures the IEEE C37.94 optical interface. IEEE C37.94
           standard constitutes a communications interface for interconnection
           of power protection equipment (protection relays) and transmission
           equipment using two multimode optical fibres. This communications
           standard enables transmission of N x 64 kb/s (with N ranging between
           1 and 12) to distances up to 2 km. The bit rate corresponding to N=1
           is 64 kb/s. The bit rate corresponding to N=12 is 768 kb/s.

         - 'ansit1': Configures the ANSI T1.102 interface in the agent. This
           interface corresponds with the 1544 kb/s interface used mainly in
           the United States and Canada."
    SYNTAX            INTEGER {
                          disabled (0),
                          g703e1 (1),
                          clock (2),
                          g703e0 (3),
                          datacom (4),
                          v11 (5),
                          v24 (6),
                          v35 (7),
                          v36 (8),
                          eia530 (9),
                          eia530a (10),
                          c3794 (11),
                          ansit1 (12)
                      }

ConnectorType ::=TEXTUAL-CONVENTION
    STATUS            current
    DESCRIPTION
        "Selects the input / output interface in a TDM test port. The currently
         available options are:

         - 'balanced': Selects the RJ-45 balanced connector for transmitting and
           receiving frames in a TDM test port. The nominal impedance of
           the balanced port is 120 Ohm.

         - 'unbalanced': Configures the BNC unbalanced connector for
           transmitting and receiving information in a TDM test port. The
           nominal impedance of the unbalanced port is 75 Ohm.

         - 'unspecified': Does not specify any physical connector for the test
           port. This setting could be used if when there is not a physical
           connector for a test por of when this connector is unknown."
    SYNTAX            INTEGER {
                          balanced (0),
                          unbalanced (1),
                          unspecified (2)
                      }
                      
FrameType ::=TEXTUAL-CONVENTION
    STATUS            current
    DESCRIPTION
        "Describes different accepted framing structures for ITU G.703 signals
         operating at 2048 kb/s. The frame type can be one of the following:

         - 'unframed': Unstructured data. There is not alignment sequence in
           the transmitted information and there is not a time slot structure.

         - 'pcm31': 2048 kb/s TDM frame made up of 32 time slots (TS0, TS1,...,
           TS31) of 64 kb/s each. TS0 carries the FAS and NFAS words. All other
           time slots carry user data.

         - 'pcm31c': 2048 kb/s TDM frame made up of 32 time slots (TS0, TS1,...,
           TS31) of 64 kb/s each. TS0 carries the FAS and NFAS words. The TS0
           carries also a CRC-4 multiframe structure that enables error
           detection at the receiving end. All other time slots carry user data.

         - 'pcm30': 2048 kb/s TDM frame made up of 32 time slots (TS0, TS1,...,
           TS31) of 64 kb/s each. TS0 carries the FAS and NFAS words. The TS16
           carries the CAS multiframe that provides signalling to the user time
           slots. Time slots different of TS0 and TS16 carry user data.

         - 'pcm30c': 2048 kb/s TDM frame made up of 32 time slots (TS0, TS1,...,
           TS31) of 64 kb/s each. This frame includes at the same time the CRC-4
           multiframe and the CAS multiframe. Time slots different of TX0 and
           TS16 carry user data.

         - 'sf': 1544 kb/s TDM frame made up of 193 bits and 24 time slots
           (TS0, TS1,..., TS31) of 56 kb/s or 64 kb/s each. The first bit in
           the frame defines a multiframe and carries an alignment sequence.
           Some bits in certain time slots may carry signalling through the
           robbed bit mechanism.

         - 'esf': 1544 kb/s TDM frame made up of 193 bits and 24 time slots
           (TS0, TS1,..., TS31) of 56 kb/s or 64 kb/s each. The first bit in
           the frame defines a multiframe and carries different kinds of
           information including the aligngment sequence, a data communications
           channed and a CRC-6 frame check sequence. Some bits in certain time
           slots are allowed to carry signallin through the robbed bit
           mechanism.

         - 'c3794': 2048 kb/s frame made up of 256 bits. It has an structure that
           allows variable data rate transmission from 64 kb/s to 768 kb/s in
           steps of 64 kb/s over an NRZ optical channel. The own frame defines a
           bit encoding mechanism that ensures proper clock recovery."
    REFERENCE
        "- ITU-T G.703: 'Physical / electrical characteristics of hierarchical
           digital interfaces'.

         - ITU-T G.704: Synchronous frame structures used at 1544, 6312, 2048,
           8448 and 44736 kbit/s hierarchical levels'.

         - ITU-T G.706: Frame Alignment and Cyclic Redundancy Check (CRC)
           procedures relating to basic frame structures defined in
           Recommendation G.704.
           
         - ANSI T1.102: Digital Hierarchy - Electrical Interfaces.
         
         - ANSI T1.403: Network and Customer Installation Interfaces - DS1
           Electrical Interface.
           
         - IEEE C37.94: IEEE Standard for N Times 64 Kilobit Per Second Optical
           Fiber Interfaces Between Teleprotection and Multiplexer Equipment."
    SYNTAX            INTEGER {
                          unframed (0),
                          pcm31 (1),
                          pcm31c (2),
                          pcm30 (3),
                          pcm30c (4),
                          sf (5),
                          esf (6),
                          c3794 (7)
                      }

TimeSlotUse ::=TEXTUAL-CONVENTION
    STATUS            current
    DESCRIPTION
        "Defines the content and source / destination of each time slot that
         furnish the 2048 kb/s TDM signal. Agents may fill the time slots with
         internally generated patterns for test purposes or they can add / drop
         external signals. The possible values for the time slot content are:

         - 'none': Empty time slot. No content is specified for the time slot.
           It can be either noise or an all zero signal, depending on the agent.

         - 'pattern': The time slot is connected to a test pattern generation or
           analysis block. This is the correct configuration for BER testing.

         - 'tone':  This setting is used for time slots connected to the tone
           generator. If there are several time slots connected to the tone
           generator, all them will carry the same tone. That means that tone
           level, frequency and phase will be the same for all time slots.

         - 'audio': The selected time slots are connected to external analogue
           input / output. This input / output can be connected to a microphone
           and speakers. The signal from the microphone is converted to a G.711
           format and sent in the E1 multiplex. In the receiving end, the
           speech signal is dropped to an analogue output where it can be
           heard through an external speaker.

         - 'adddrop':  The selected time slots connected to an external digital
           low speed input / output (G.703 codirectional or datacom, for
           example).

         - 'rx': Time slots received the corresponding port input are bypassed
           to the port output without alterations. TS0 and TS16 can be set to
           the bypass option even not containing user information. This option
           is only available if the TDM test port is configured in through mode
           (for example, 'tdmGenMode' configured to 'e1Through').

         - 'overhead': It is used for time slots not available for user
           configuration (FAS / NFAS, CAS)."
    SYNTAX            INTEGER {
                          none (0),
                          pattern (1),
                          tone (2),
                          audio (3),
                          adddrop (4),
                          rx (5),
                          overhead (6)
                      }

ABCD ::=TEXTUAL-CONVENTION
    DISPLAY-HINT      "d"
    STATUS            current
    DESCRIPTION
        "Textual convention that encodes the value of the four ABCD signalling
         bits assigned to a time slot in the CAS signalling mechanism."
    SYNTAX            Unsigned32 (0..15)

--
-- Top level module structure
--

tdmPortControl      OBJECT IDENTIFIER ::= { tdmPort 1 }

--
-- Transmission enable / disable control group
--

tdmPortEnable OBJECT-TYPE
    SYNTAX            TruthValue
    MAX-ACCESS        read-write
    STATUS            current
    DESCRIPTION
        "Starts / Stops traffic generation in the managed entity. The action
         starts generation through all the available blocks. The number of
         monitoring blocks may not be the same for different managed entities
         and it may be that there is only one monitoring block for some of
         them."
    ::= { tdmPortControl 1 }

tdmPortMode OBJECT-TYPE
    SYNTAX            OperationMode
    MAX-ACCESS        read-write
    STATUS            current
    DESCRIPTION
        "Configures the general operation mode for the agent. It determines the
         functionality, supported frame formats, protocols and tests. Some
         configuration fields defined by several OIDs defined in this MIB may
         not be available in some configuration modes.

         The operation mode usually involves automatic re-configuration of all
         the available test ports in the agent.
         
         Note that this OID is deprecated, as the main mode of operation
         must be selected in the 'mfFuncTable' defined in the
         ATSL-MULTIFUNCTION-MIB.  Setting the operation mode directly in
         this OID may result in an inconsistent behaviour of the agent,
         especially in those testers that implement multiple functions,
         apart from the TDM function."
         
    ::= { tdmPortControl 2 }

--
--  Mode configuration table
--

tdmPortModeTable OBJECT-TYPE
    SYNTAX            SEQUENCE OF TdmPortModeEntry
    MAX-ACCESS        not-accessible
    STATUS            current
    DESCRIPTION
        "This table can be used for test port management in the agent. It
         contains one row per each test port and it can be used to configure 
         the interface in ports supporting multiple interface operation. For
         test ports supporting only a single operation mode, this table enables
         the SNMP manager to read information about the interface. 

         Interfaces available for configuration depend on the global operation
         mode configured with 'tdmPortMode'. Depending on the interface types
         configured in this table some OIDs may be enabled or disabled in other
         tables or MIBs."
    ::= { tdmPort 2 }

tdmPortModeEntry OBJECT-TYPE
    SYNTAX            TdmPortModeEntry
    MAX-ACCESS        not-accessible
    STATUS            current
    DESCRIPTION
        "Table entry containing control commands applicable to a particular
         traffic generation block."
    INDEX { tdmPortModeIndex }
    ::= { tdmPortModeTable 1 }

TdmPortModeEntry ::= SEQUENCE {
    tdmPortModeIndex              TableIndex,
    tdmPortModeBlockName          DisplayString,
    tdmPortModeInterface          TdmInterface,
    tdmPortModeStatus             RowStatus
}

tdmPortModeIndex OBJECT-TYPE
    SYNTAX            TableIndex
    MAX-ACCESS        not-accessible
    STATUS            current
    DESCRIPTION
        "A unique value, greater than zero, for each traffic generation
         block. It is recommended that values are assigned contiguously
         starting from 1. The value for each block index must remain constant
         at least from one re-initialization of the entity's network management
         to the next re-initialization."
    ::= { tdmPortModeEntry 2 }

tdmPortModeBlockName OBJECT-TYPE
    SYNTAX            DisplayString
    MAX-ACCESS        read-only
    STATUS            current
    DESCRIPTION
        "The textual name of the processing block. This might be an interface
         text name, such as 'eth0' or a stream identifier such as 'eth0.0'
         depending on the capabilities available in the managed entity.

         Other capture, filtering or statistics block associated to the same
         traffic generation block within the same managed device must use the
         same textual name whenever possible."
    ::= { tdmPortModeEntry 3 }

tdmPortModeInterface OBJECT-TYPE
    SYNTAX            TdmInterface
    MAX-ACCESS        read-write
    STATUS            current
    DESCRIPTION
        "In test ports supporting multiple communications interfaces, such as
         datacom ports, this OID defines the current interface. Normally, the
         values available for configuration are a subset of the interface
         identifiers defined in a 'TdmInterface' text convention."
    ::= { tdmPortModeEntry 4 }

tdmPortModeStatus OBJECT-TYPE
    SYNTAX            RowStatus
    MAX-ACCESS        read-create
    STATUS            current
    DESCRIPTION
        "Status column for 'tdmPortModeTable'. Enables dynamic creation / 
         deletion of table entries in the current table. Information contained
         in the table entry may not be available for read / write operations
         if the status column is set to something different to 'active'. See
         the REFERENCEd documents to get more information about the encoding
         and use of the status column."
    REFERENCE 
        "- IETF RFC 2579: 'Textual Conventions for SMIv2'."
    ::= { tdmPortModeEntry 5 }

--
--  BER test pattern configuration table
--

tdmPortPatternTable OBJECT-TYPE
    SYNTAX            SEQUENCE OF TdmPortPatternEntry
    MAX-ACCESS        not-accessible
    STATUS            current
    DESCRIPTION
        "This table configures the test pattern format for traffic synthetic
         traffic internally generated by the agent.

         Most of the agents with frame generation capabilities generate
         synthetic traffic with configurable content. The bit stream transmitted
         by frame generators enable them to carry out different kinds of
         measurements including Bit Error Rate (BER), latency and several other
         derived parameters."
    ::= { tdmPort 3 }

tdmPortPatternEntry OBJECT-TYPE
    SYNTAX            TdmPortPatternEntry
    MAX-ACCESS        not-accessible
    STATUS            current
    DESCRIPTION
        "Table entry containing control commands applicable to a particular
         traffic generation block."
    INDEX { tdmPortPatternIndex }
    ::= { tdmPortPatternTable 1 }

TdmPortPatternEntry ::= SEQUENCE {
    tdmPortPatternIndex          TableIndex,
    tdmPortPatternBlockName      DisplayString,
    tdmPortPatternTx             TestPattern,
    tdmPortPatternTxFixed        Word32,
    tdmPortPatternRx             TestPattern,
    tdmPortPatternRxFixed        Word32,
    tdmPortPatternStatus         RowStatus
}

tdmPortPatternIndex OBJECT-TYPE
    SYNTAX            TableIndex
    MAX-ACCESS        not-accessible
    STATUS            current
    DESCRIPTION
        "A unique value, greater than zero, for each traffic generation
         block. It is recommended that values are assigned contiguously
         starting from 1. The value for each block index must remain constant
         at least from one re-initialization of the entity's network
         management to the next re-initialization."
    ::= { tdmPortPatternEntry 1 }

tdmPortPatternBlockName OBJECT-TYPE
    SYNTAX            DisplayString
    MAX-ACCESS        read-only
    STATUS            current
    DESCRIPTION
        "The textual name of the processing block. This might be an interface
         text name, such as 'eth0' or a stream identifier such as 'eth0.0'
         depending on the capabilities available in the managed entity.

         Other capture, filtering or statistics block associated to the same
         traffic generation block within the same managed device must use the
         same textual name whenever possible."
    ::= { tdmPortPatternEntry 2 }

tdmPortPatternTx OBJECT-TYPE
    SYNTAX            TestPattern
    MAX-ACCESS        read-write
    STATUS            current
    DESCRIPTION
        "Sets the transmitted Bit Error Rate (BER) test pattern. Test patterns
         are usually Pseudo-Random Bit Sequences (PRBS) or other bit sequences
         designed to measure certain network parameters like the BER."
    ::= { tdmPortPatternEntry 3 }

tdmPortPatternTxFixed OBJECT-TYPE
    SYNTAX            Word32
    MAX-ACCESS        read-write
    STATUS            current
    DESCRIPTION
        "This field specifies the value of a 32-bit user configurable pattern
         that fills the frame user content of the internally generated packets
         in the current traffic generation block.

         Configuration of 'tdmPortPatternTxFixed' requires 'psnPortPatternTx'
         to be configured to 'user'."
    ::= { tdmPortPatternEntry 4 }

tdmPortPatternRx OBJECT-TYPE
    SYNTAX            TestPattern
    MAX-ACCESS        read-write
    STATUS            current
    DESCRIPTION
        "Sets the expected Bit Error Rate (BER) test pattern. Test patterns
         are usually Pseudo-Random Bit Sequences (PRBS) or other bit sequences
         designed to measure certain network parameters like the BER."
    ::= { tdmPortPatternEntry 5 }

tdmPortPatternRxFixed OBJECT-TYPE
    SYNTAX            Word32
    MAX-ACCESS        read-write
    STATUS            current
    DESCRIPTION
        "This field specifies the value of a 32-bit user configurable pattern
         the agent is expecting in the receiver of an specific test port.

         Configuration of 'tdmPortPatternRxFixed' requires 'psnPortPatternRx'
         to be configured to 'user'."
    ::= { tdmPortPatternEntry 6 }

tdmPortPatternStatus OBJECT-TYPE
    SYNTAX            RowStatus
    MAX-ACCESS        read-create
    STATUS            current
    DESCRIPTION
        "Status column for 'e1PortPatternTable'. Enables dynamic creation / 
         deletion of table entries in the current table. Information contained
         in the table entry may not be available for read / write operations
         if the status column is set to something different to 'active'. See
         the REFERENCEd documents to get more information about the encoding
         and use of the status column."
    REFERENCE 
        "- IETF RFC 2579: 'Textual Conventions for SMIv2'."
    ::= { tdmPortPatternEntry 7 }

END
